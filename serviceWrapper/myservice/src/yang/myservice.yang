module myservice {
  namespace "http://com/example/myservice";
  prefix myservice;

  import ietf-inet-types {
    prefix inet;
  }
  import tailf-ncs {
    prefix ncs;
  }

  list myservice {
    key name;

    uses ncs:service-data;
    ncs:servicepoint "myservice";

    leaf name {
      type string;
    }

    // may replace this with other ways of refering to the devices.
    leaf device1 {
      type leafref {
        path "/ncs:devices/ncs:device/ncs:name";
      }
    }

    leaf device2 {
      type leafref {
        path "/ncs:devices/ncs:device/ncs:name";
      }
    }

    // replace with your own stuff here
    leaf dummy {
      type inet:ipv4-address;
    }
  }
}
